FME workspace bg_stars.fmw

Parameters:
- DestDataset_ESRISHAPE = C:\Users\Vakarian\Documents\A - Omat\Larpit\Odysseus\shp   # Destination Esri Shapefile Folder
- DestDataset_POSTGIS = Odysseus-local   # Connection

Writers:
- ESRISHAPE_1: ESRISHAPE to $(DestDataset_ESRISHAPE) in EPSG:3857
- POSTGIS_1: POSTGIS to $(DestDataset_POSTGIS)

Creator
    COORDS = 0 0
    COORDSYS = EPSG:3857
    GEOMTYPE = 2D Coordinate List
    NUM = 3000
    CREATED -> RandomNumberGenerator
Note: shp
bg_stars (writer ESRISHAPE_1) [off]
    attributes: x char(200), y char(200), size char(200), size_scale char(200), size_halo char(200), fill_opaci char(200), color_star char(200), color_halo char(200)
AttributeManager
    ATTR_TABLE:
      REMOVE x
      REMOVE y
      RENAME_SET_VALUE size > gs_size
      RENAME_SET_VALUE size_scale > gs_size_scale
      RENAME_SET_VALUE size_halo > gs_size_halo
      RENAME_SET_VALUE color_star > gs_color
      RENAME_SET_VALUE color_halo > gs_color_halo
      RENAME_SET_VALUE fill_opaci > gs_fill_opacity
      SET_TO gs_rotation = 0
    -> starmap_bg (writer POSTGIS_1)
Note: postgis
starmap_bg (writer POSTGIS_1)
    attributes: gs_color varchar(200), gs_color_halo varchar(200), gs_rotation int8, gs_size float4, gs_size_scale float4, gs_size_halo float4, gs_fill_opacity float4

Bookmark: xy
RandomNumberGenerator
    MAX = "20026376.39 "
    MIN = -20026376.39
    PLACES = 2
    RESULT_ATTR = x
    -> RandomNumberGenerator_2
RandomNumberGenerator_2
    MAX = 20048966.10
    MIN = "-20048966.10 "
    PLACES = 2
    RESULT_ATTR = y
    -> CoordinateReplacer
CoordinateReplacer
    FIND_X = 0
    FIND_Y = 0
    REPLACE_X = @Value(x)
    REPLACE_Y = @Value(y)
    -> Sampler
Sampler
    RATE = 10
    SAMPLE_MODE = Yes
    SAMPLE_TYPE_LONG = Every Nth Feature
    SAMPLED -> Size
    NOT_SAMPLED -> Size_2

Bookmark: Size
Size: RandomNumberGenerator
    MAX = 1.1
    MIN = 0.1
    PLACES = 1
    RESULT_ATTR = size
    -> Size_scale
Size_2: RandomNumberGenerator
    MAX = 0.5
    MIN = 0.1
    PLACES = 1
    RESULT_ATTR = size
    -> Size_scale
Size_scale: RandomNumberGenerator
    MAX = 1.2
    MIN = 1
    PLACES = 2
    RESULT_ATTR = size_scale
    -> Size_halo
Size_halo: RandomNumberGenerator
    MAX = 12
    MIN = 2
    PLACES = 1
    RESULT_ATTR = size_halo
    -> Fill_opacity
Fill_opacity: RandomNumberGenerator
    MAX = 0.7
    MIN = 0.4
    PLACES = 1
    RESULT_ATTR = fill_opaci
    -> RandomNumberGenerator_6

Bookmark: Color
RandomNumberGenerator_6
    MAX = 14
    MIN = 1
    PLACES = 0
    RESULT_ATTR = color
    -> StringPairReplacer
StringPairReplacer
    CASE = no
    MAP:
      10 #F9F6CF
      11 #666EFF
      12 #8B96FF
      13 #FEAA52
      14 #FA6642
      1 #F9F3A4
      2 #FFF464
      3 #CBCDFE
      4 #CBCDFE
      5 #E6E6F7
      6 #FFFFFF
      7 #FFFFFF
      8 #FFFFFF
      9 #FFFFFF
    RESULT_ATTR = color_star
    SRC_ATTR = color
    -> StringPairReplacer_2
StringPairReplacer_2
    CASE = no
    MAP:
      10 F9F6CF
      11 666EFF
      12 8B96FF
      13 FEAA52
      14 FA6642
      1 F9F3A4
      2 FFF464
      3 CBCDFE
      4 CBCDFE
      5 E6E6F7
      6 FFFFFF
      7 FFFFFF
      8 FFFFFF
      9 FFFFFF
    RESULT_ATTR = color_halo
    SRC_ATTR = color
    -> AttributeKeeper

Bookmark: Cleaning
AttributeKeeper
    KEEP_ATTRS = y,size_scale,x,color_halo,size,size_halo,color_star,fill_opaci
    -> AttributeManager
    -> bg_stars (writer ESRISHAPE_1)
