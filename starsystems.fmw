FME workspace starsystems.fmw

Parameters:
- DestDataset_ESRISHAPE = C:\Users\Vakarian\Documents\A - Omat\Larpit\Odysseus\shp   # Destination Esri Shapefile Folder
- DestDataset_POSTGIS = Odysseus-local   # Connection

Writers:
- ESRISHAPE_1: ESRISHAPE to $(DestDataset_ESRISHAPE) in EPSG:3857
- POSTGIS_2: POSTGIS to $(DestDataset_POSTGIS)

AttributeKeeper_2_Output: Inspector [off]
nebula (writer ESRISHAPE_1) [off]
    attributes: x char(200), y char(200), size char(200), size_scale char(200), size_halo char(200), fill_opaci char(200), color_halo char(200), color_star char(200)
Creator
    COORDS = 0 0
    COORDSYS = EPSG:3857
    GEOMTYPE = 2D Coordinate List
    NUM = 700
    CREATED -> RandomNumberGenerator
Random_type_6: RandomNumberGenerator
    MAX = 5
    MIN = 1
    PLACES = 0
    RESULT_ATTR = atmosphere
    -> StringPairReplacer_10
StringPairReplacer_10
    CASE = no
    MAP:
      1 Oxygen,\ Natrium,\ Hydrogen
      2 Carbon\ dioxide,\ Nitrogen
      3 Nitrogen,\ Oxygen,\ Argon
      4 Carbon\ dioxide,\ Nitrogen,\ Argon
      5 Nitrogen,\ Oxygen,\ Carbon\ dioxide
    RESULT_ATTR = atmosphere
    SRC_ATTR = atmosphere
    -> Random_temperature
Random_temperature: RandomNumberGenerator
    MAX = 90
    MIN = 50
    PLACES = 0
    RESULT_ATTR = temperature
    -> AttributeRounder
Duplicate_Names_AsteroidComet: Inspector
AttributeKeeper
    KEEP_ATTRS = radius,category,satellite_of,orbital_period,category0,gs-size,gs-size_scale,atm_pressure,category1,name_generated,celestial_body,gs-color_halo,gs-size_halo,habitable_zone,gs-rotation,distance,temperature,gs-color,mass,atmosphere,gs-fill_opaci,name_known,rotation,orbiter_count
    -> Tester_19
Random_num: RandomNumberGenerator
    MAX = 9
    MIN = 0
    PLACES = 0
    RESULT_ATTR = _random_number
    -> Random_num_2
Random_num_2: RandomNumberGenerator
    MAX = 9
    MIN = 0
    PLACES = 0
    RESULT_ATTR = _random_number2
    -> RandomLetter
RandomLetter: RandomNumberGenerator
    MAX = 26
    MIN = 1
    PLACES = 0
    RESULT_ATTR = _random_letter
    -> StringPairReplacer_15
StringPairReplacer_15
    CASE = no
    MAP:
      26 Z
      25 Y
      24 X
      23 W
      22 V
      21 U
      20 T
      19 S
      18 R
      17 Q
      16 P
      15 O
      14 N
      13 M
      12 L
      11 K
      10 J
      9 I
      8 H
      7 G
      6 F
      5 E
      4 D
      3 C
      2 B
      1 A
    RESULT_ATTR = _random_letter
    SRC_ATTR = _random_letter
    -> Random_num_3
Random_num_3: RandomNumberGenerator
    MAX = 9
    MIN = 0
    PLACES = 0
    RESULT_ATTR = _random_number3
    -> Random_num_4
Random_num_4: RandomNumberGenerator
    MAX = 9
    MIN = 0
    PLACES = 0
    RESULT_ATTR = _random_number4
    -> RandomLetter_2
RandomLetter_2: RandomNumberGenerator
    MAX = 26
    MIN = 1
    PLACES = 0
    RESULT_ATTR = _random_letter2
    -> StringPairReplacer_20
StringPairReplacer_20
    CASE = no
    MAP:
      26 Z
      25 Y
      24 X
      23 W
      22 V
      21 U
      20 T
      19 S
      18 R
      17 Q
      16 P
      15 O
      14 N
      13 M
      12 L
      11 K
      10 J
      9 I
      8 H
      7 G
      6 F
      5 E
      4 D
      3 C
      2 B
      1 A
    RESULT_ATTR = _random_letter2
    SRC_ATTR = _random_letter2
    -> AttributeCreator_31
AttributeCreator_31
    ATTR_TABLE:
      SET_TO surface_gravity = @round(@div(@div(@mult(@Value(mass),6.6742E-11),@mult(@Value(radius),1000,1000,@Value(radius))),10),4)
      SET_TO description = FME_NULL_VALUE
      SET_TO ghligh = @Value(category1)-@Value(category0)@Value(_random_number)@Value(_random_number2)-@Value(_random_letter)@Value(_random_letter2)@Value(_random_number3)@Value(_random_number4)
    -> AttributeFilter_2
AttributeFilter_2
    ATTR_NAME = celestial_body
    ATTR_VALUES = <Empty>,<Missing>,<Null>,<Unfiltered>,comet,asteroid,star,planet,natural satellite
    comet -> AttributeCreator_32
    asteroid -> AttributeCreator_33
    star -> AttributeFilter_2_star
    star -> NullAttributeMapper
    planet -> AttributeFilter_2_planet
    planet -> NullAttributeMapper
    natural satellite -> AttributeCreator_36
AttributeCreator_32
    ATTR_TABLE = SET_TO name_generated = C@Value(category0)-@Value(_random_letter)@Value(_random_letter2)@Value(_random_number)@Value(_random_number2)@Value(_random_number3)
    -> AttributeFilter_2_comet
    -> NullAttributeMapper
AttributeFilter_2_comet: Inspector [off]
AttributeCreator_33
    ATTR_TABLE = SET_TO name_generated = A@Value(category0)-@Value(_random_letter)@Value(_random_letter2)@Value(_random_number)@Value(_random_number2)@Value(_random_number3)
    -> AttributeFilter_2_asteroid
    -> NullAttributeMapper
AttributeFilter_2_asteroid: Inspector [off]
AttributeFilter_2_star: Inspector [off]
AttributeFilter_2_planet: Inspector [off]
AttributeCreator_36
    ATTR_TABLE = SET_TO name_generated = @Value(category0)@Value(_random_number)@Value(_random_number2)-@Value(_random_letter)@Value(_random_letter2)@Value(_random_number3)@Value(_random_number4)
    -> AttributeFilter_2_moon
    -> NullAttributeMapper
NullAttributeMapper
    ATTRCHOICE = Selected Attributes
    ATTRLIST = gs-size_scale habitable_zone orbital_period celestial_body mass gs-size orbiter_count name_known radius gs-rotation ring_system gs-size_halo rotation atmosphere gs-color atm_pressure temperature category distance gs-fill_opaci name_generated gs-color_halo
    NULL_TREATMENT = Null
    SOURCE_ATTR_VAL = Empty "Missing (Selected Attributes Only)"
    -> AttributeKeeper_3
AttributeKeeper_3
    KEEP_ATTRS = radius,category,satellite_of,orbital_period,ring_system,gs-size,gs-size_scale,atm_pressure,name_generated,celestial_body,gs-color_halo,gs-size_halo,habitable_zone,gs-rotation,distance,temperature,gs-color,mass,atmosphere,gs-fill_opaci,name_known,rotation,description,surface_gravity,orbiter_count
    -> DuplicateFilter_4
DuplicateFilter_4
    INPUT_ORDERED_CHOICE = No
    KEYATTR = name_generated
    UNIQUE -> AttributeManager
    DUPLICATE -> DuplicateFilter_4_Duplicate
DuplicateFilter_4_Duplicate: Inspector
AttributeManager
    ATTR_TABLE:
      RENAME_SET_VALUE gs-size > gs_size
      RENAME_SET_VALUE gs-size_scale > gs_size_scale
      RENAME_SET_VALUE gs-size_halo > gs_size_halo
      RENAME_SET_VALUE gs-color > gs_color
      RENAME_SET_VALUE gs-color_halo > gs_color_halo
      RENAME_SET_VALUE gs-fill_opaci > gs_fill_opacity
      RENAME_SET_VALUE gs-rotation > gs_rotation
      SET_TO is_scanned = 0
    -> AttributeRounder_2
AttributeRounder_2
    PLACES = 2
    ROUND_TYPE = Nearest
    SRC_ATTRS = surface_gravity distance
    -> Ring_system
Ring_system: StringPairReplacer
    CASE = no
    MAP:
      Yes 1
      No  0
    RESULT_ATTR = ring_system
    SRC_ATTR = ring_system
    -> AttributeTrimmer
AttributeTrimmer
    SRC_ATTRS = gs_size
    TRIM_CHARS = "\n"
    TRIM_TO_NONE = Yes
    TRIM_TYPE = Both
    -> starmap_object (writer POSTGIS_2)
    -> All
All: Inspector [off]
starmap_object (writer POSTGIS_2)
    attributes: name_generated varchar(200), surface_gravity float8, description text, ring_system bool, distance float8, radius int8, mass numeric(35,0), habitable_zone varchar(200), name_known varchar(200), celestial_body varchar(200), atmosphere varchar(255), satellite_of varchar(200), category varchar(200), temperature int8, orbital_period float8, rotation float8, orbiter_count int8, atm_pressure float8, gs_size float4, gs_size_scale float4, gs_size_halo float4, gs_color varchar(200), gs_color_halo varchar(200), gs_fill_opacity float4, gs_rotation int8, is_scanned bool
AttributeFilter_2_moon: Inspector [off]

Bookmark: Middle star of Alpha Quadrant
Creator_2 [off]
    COORDS = 0 0
    COORDSYS = EPSG:3857
    GEOMTYPE = 2D Coordinate List
    NUM = 1
    CREATED -> AttributeCreator
AttributeCreator [off]
    ATTR_TABLE:
      SET_TO x = 5006594.0975
      SET_TO y = -5012241.525
      SET_TO size = 2
      SET_TO size_scale = 1.3
      SET_TO size_halo = 2
      SET_TO color_star = #FEAA52
      SET_TO fill_opaci = 0.9
      SET_TO color_halo = FEAA52
    -> CoordinateReplacer_2
CoordinateReplacer_2 [off]
    FIND_X = 0
    FIND_Y = 0
    REPLACE_X = @Value(x)
    REPLACE_Y = @Value(y)
    -> AttributeKeeper_2
AttributeKeeper_2 [off]
    KEEP_ATTRS = y,size,fill_opaci,size_scale,color_star,size_halo,x,color_halo
    -> nebula (writer ESRISHAPE_1)
    -> AttributeKeeper_2_Output

Bookmark: xy
RandomNumberGenerator
    MAX = "20026376.39 "
    MIN = -20026376.39
    PLACES = 2
    RESULT_ATTR = x
    -> RandomNumberGenerator_2
RandomNumberGenerator_2
    MAX = 20048966.10
    MIN = "-20048966.10 "
    PLACES = 2
    RESULT_ATTR = y
    -> CoordinateReplacer
CoordinateReplacer
    FIND_X = 0
    FIND_Y = 0
    REPLACE_X = @Value(x)
    REPLACE_Y = @Value(y)
    -> Size

Bookmark: Size
Size: RandomNumberGenerator
    MAX = 1
    MIN = 0.3
    PLACES = 1
    RESULT_ATTR = gs-size
    -> Size_scale
Size_scale: RandomNumberGenerator
    MAX = 1.8
    MIN = 1.1
    PLACES = 2
    RESULT_ATTR = gs-size_scale
    -> Size_halo
Size_halo: RandomNumberGenerator
    MAX = 2
    MIN = 1
    PLACES = 1
    RESULT_ATTR = gs-size_halo
    -> Fill_opacity
Fill_opacity: RandomNumberGenerator
    MAX = 0.7
    MIN = 0.4
    PLACES = 1
    RESULT_ATTR = gs-fill_opaci
    -> Sampler_a

Bookmark: Extra celestial bodies
Sampler_a
    RATE = 500
    SAMPLE_MODE = Yes
    SAMPLE_TYPE_LONG = First N Features
    SAMPLED -> Random_color
    NOT_SAMPLED -> Sampler_a_2
Sampler_a_2
    RATE = 70
    SAMPLE_MODE = Yes
    SAMPLE_TYPE_LONG = First N Features
    SAMPLED -> Random_rotation
    NOT_SAMPLED -> Random_type

Bookmark: Color
Random_color: RandomNumberGenerator
    MAX = 14
    MIN = 1
    PLACES = 0
    RESULT_ATTR = gs-color
    -> StringPairReplacer
StringPairReplacer
    CASE = no
    MAP:
      10 F9F6CF
      11 666EFF
      12 8B96FF
      13 FEAA52
      14 FA6642
      1 F9F3A4
      2 FFF464
      3 CBCDFE
      4 CBCDFE
      5 E6E6F7
      6 FFFFFF
      7 FFFFFF
      8 FFFFFF
      9 FFFFFF
    RESULT_ATTR = gs-color_halo
    SRC_ATTR = gs-color
    -> AttributeCreator_2
AttributeCreator_2
    ATTR_TABLE = SET_TO gs-color = #@Value(gs-color_halo)
    -> Random_rotation_5

Bookmark: Attributes - temperature - radius - mass - luminocity - habitable zone
Random_rotation_5: RandomNumberGenerator
    MAX = 100
    MIN = 0.1
    PLACES = 1
    RESULT_ATTR = rotation
    -> StringPairReplacer_2
StringPairReplacer_2
    CASE = no
    MAP:
      #666EFF O3
      #8B96FF B0
      #CBCDFE A0
      #E6E6F7 A5
      #FFFFFF F0
      #F9F6CF G0
      #F9F3A4 G5
      #FFF464 K0
      #FEAA52 M0
      #FA6642 M8
    RESULT_ATTR = category
    SRC_ATTR = gs-color
    -> AttributeCreator_3
AttributeCreator_3
    ATTR_TABLE:
      SET_TO celestial_body = star
      SET_TO temperature = FME_NULL_VALUE
      SET_TO radius = FME_NULL_VALUE
      SET_TO mass = FME_NULL_VALUE
      SET_TO luminosity = FME_NULL_VALUE
      SET_TO habitable_zone = FME_NULL_VALUE
      SET_TO distance = 0
      SET_TO orbital_period = FME_NULL_VALUE
      SET_TO atmosphere = No
    -> Random_planet_count
Random_planet_count: RandomNumberGenerator
    MAX = 10
    MIN = 3
    PLACES = 0
    RESULT_ATTR = orbiter_count
    -> AttributeFilter
AttributeFilter
    ATTR_NAME = category
    ATTR_VALUES = <Empty>,<Missing>,<Null>,<Unfiltered>,O3,B0,A0,A5,F0,G0,G5,K0,M0,M8
    O3 -> Random_temp_O3
    B0 -> Random_temp_B0
    A0 -> Random_temp_A0
    A5 -> Random_temp_A5
    F0 -> Random_temp_F0
    G0 -> Random_temp_G0
    G5 -> Random_temp_G5
    K0 -> Random_temp_K0
    M0 -> Random_temp_M0
    M8 -> Random_temp_M8
Random_temp_O3: RandomNumberGenerator
    MAX = 55000
    MIN = 35000
    PLACES = 0
    RESULT_ATTR = temperature
    -> Random_radius_O3
Random_radius_O3: RandomNumberGenerator
    MAX = 17
    MIN = 8.5
    PLACES = 2
    RESULT_ATTR = radius
    -> Random_mass_O3
Random_mass_O3: RandomNumberGenerator
    MAX = 150
    MIN = 23
    PLACES = 2
    RESULT_ATTR = mass
    -> Random_lum_O3
Random_lum_O3: RandomNumberGenerator
    MAX = 1500000
    MIN = 170000
    PLACES = 0
    RESULT_ATTR = luminosity
    -> Random_hb_O3
Random_hb_O3: RandomNumberGenerator
    MAX = 1300
    MIN = 410
    PLACES = 0
    RESULT_ATTR = habitable_zone
    -> SubstringExtractor
Random_temp_B0: RandomNumberGenerator
    MAX = 35000
    MIN = 12000
    PLACES = 0
    RESULT_ATTR = temperature
    -> Random_radius_B0_2
Random_radius_B0_2: RandomNumberGenerator
    MAX = 8.5
    MIN = 3
    PLACES = 2
    RESULT_ATTR = radius
    -> Random_mass_B0
Random_mass_B0: RandomNumberGenerator
    MAX = 23
    MIN = 3.8
    PLACES = 1
    RESULT_ATTR = mass
    -> Random_lum_B0
Random_lum_B0: RandomNumberGenerator
    MAX = 170000
    MIN = 180
    PLACES = 0
    RESULT_ATTR = luminosity
    -> Random_hb_B0
Random_hb_B0: RandomNumberGenerator
    MAX = 410
    MIN = 13
    PLACES = 0
    RESULT_ATTR = habitable_zone
    -> SubstringExtractor
Random_temp_A0: RandomNumberGenerator
    MAX = 12000
    MIN = 8800
    PLACES = 0
    RESULT_ATTR = temperature
    -> Random_radius_A0
Random_radius_A0: RandomNumberGenerator
    MAX = 3
    MIN = 2
    PLACES = 2
    RESULT_ATTR = radius
    -> Random_mass_A0
Random_mass_A0: RandomNumberGenerator
    MAX = 3.8
    MIN = 2.5
    PLACES = 2
    RESULT_ATTR = mass
    -> Random_lum_A0
Random_lum_A0: RandomNumberGenerator
    MAX = 180
    MIN = 35
    PLACES = 0
    RESULT_ATTR = luminosity
    -> Random_hb_A0
Random_hb_A0: RandomNumberGenerator
    MAX = 13
    MIN = 5
    PLACES = 1
    RESULT_ATTR = habitable_zone
    -> SubstringExtractor
Random_temp_A5: RandomNumberGenerator
    MAX = 8800
    MIN = 7700
    PLACES = 0
    RESULT_ATTR = temperature
    -> Random_radius_A5
Random_radius_A5: RandomNumberGenerator
    MAX = 2
    MIN = 1.6
    PLACES = 2
    RESULT_ATTR = radius
    -> Random_mass_A5
Random_mass_A5: RandomNumberGenerator
    MAX = 2.5
    MIN = 1.8
    PLACES = 2
    RESULT_ATTR = mass
    -> Random_lum_A5
Random_lum_A5: RandomNumberGenerator
    MAX = 35
    MIN = 10
    PLACES = 0
    RESULT_ATTR = luminosity
    -> Random_hb_A5
Random_hb_A5: RandomNumberGenerator
    MAX = 5
    MIN = 3.1
    PLACES = 1
    RESULT_ATTR = habitable_zone
    -> SubstringExtractor
Random_temp_F0: RandomNumberGenerator
    MAX = 7700
    MIN = 6400
    PLACES = 0
    RESULT_ATTR = temperature
    -> Random_radius_F0
Random_radius_F0: RandomNumberGenerator
    MAX = 1.6
    MIN = 1.3
    PLACES = 2
    RESULT_ATTR = radius
    -> Random_mass_F0
Random_mass_F0: RandomNumberGenerator
    MAX = 1.8
    MIN = 1.3
    PLACES = 2
    RESULT_ATTR = mass
    -> Random_lum_F0
Random_lum_F0: RandomNumberGenerator
    MAX = 10
    MIN = 3.2
    PLACES = 1
    RESULT_ATTR = luminosity
    -> Random_hb_F0
Random_hb_F0: RandomNumberGenerator
    MAX = 3.1
    MIN = 1.8
    PLACES = 1
    RESULT_ATTR = habitable_zone
    -> SubstringExtractor
Random_temp_G0: RandomNumberGenerator
    MAX = 6400
    MIN = 5800
    PLACES = 0
    RESULT_ATTR = temperature
    -> Random_radius_G0
Random_radius_G0: RandomNumberGenerator
    MAX = 1.3
    MIN = 1
    PLACES = 2
    RESULT_ATTR = radius
    -> Random_mass_G0
Random_mass_G0: RandomNumberGenerator
    MAX = 1.3
    MIN = 1
    PLACES = 2
    RESULT_ATTR = mass
    -> Random_lum_G0
Random_lum_G0: RandomNumberGenerator
    MAX = 3.2
    MIN = 1
    PLACES = 2
    RESULT_ATTR = luminosity
    -> Random_hb_G0
Random_hb_G0: RandomNumberGenerator
    MAX = 1.8
    MIN = 1
    PLACES = 2
    RESULT_ATTR = habitable_zone
    -> SubstringExtractor
Random_temp_G5: RandomNumberGenerator
    MAX = 5800
    MIN = 5500
    PLACES = 0
    RESULT_ATTR = temperature
    -> Random_radius_G5
Random_radius_G5: RandomNumberGenerator
    MAX = 1
    MIN = 0.89
    PLACES = 2
    RESULT_ATTR = radius
    -> Random_mass_G5
Random_mass_G5: RandomNumberGenerator
    MAX = 1
    MIN = 0.85
    PLACES = 2
    RESULT_ATTR = mass
    -> Random_lum_G5
Random_lum_G5: RandomNumberGenerator
    MAX = 1
    MIN = 0.55
    PLACES = 2
    RESULT_ATTR = luminosity
    -> Random_hb_G5
Random_hb_G5: RandomNumberGenerator
    MAX = 1
    MIN = 0.72
    PLACES = 2
    RESULT_ATTR = habitable_zone
    -> SubstringExtractor
Random_temp_K0: RandomNumberGenerator
    MAX = 5500
    MIN = 4000
    PLACES = 0
    RESULT_ATTR = temperature
    -> Random_radius_K0
Random_radius_K0: RandomNumberGenerator
    MAX = 0.89
    MIN = 0.66
    PLACES = 2
    RESULT_ATTR = radius
    -> Random_mass_K0
Random_mass_K0: RandomNumberGenerator
    MAX = 0.85
    MIN = 0.59
    PLACES = 2
    RESULT_ATTR = mass
    -> Random_lum_K0
Random_lum_K0: RandomNumberGenerator
    MAX = 0.55
    MIN = 0.11
    PLACES = 2
    RESULT_ATTR = luminosity
    -> Random_hb_K0
Random_hb_K0: RandomNumberGenerator
    MAX = 0.72
    MIN = 0.33
    PLACES = 2
    RESULT_ATTR = habitable_zone
    -> SubstringExtractor
Random_temp_M0: RandomNumberGenerator
    MAX = 4000
    MIN = 3200
    PLACES = 0
    RESULT_ATTR = temperature
    -> Random_radius_M0
Random_radius_M0: RandomNumberGenerator
    MAX = 0.66
    MIN = 0.27
    PLACES = 2
    RESULT_ATTR = radius
    -> Random_mass_M0
Random_mass_M0: RandomNumberGenerator
    MAX = 0.59
    MIN = 0.21
    PLACES = 2
    RESULT_ATTR = mass
    -> Random_lum_M0
Random_lum_M0: RandomNumberGenerator
    MAX = 0.11
    MIN = 0.011
    PLACES = 3
    RESULT_ATTR = luminosity
    -> Random_hb_M0
Random_hb_M0: RandomNumberGenerator
    MAX = 0.33
    MIN = 0.10
    PLACES = 2
    RESULT_ATTR = habitable_zone
    -> SubstringExtractor
Random_temp_M8: RandomNumberGenerator
    MAX = 3200
    MIN = 2500
    PLACES = 0
    RESULT_ATTR = temperature
    -> Random_radius_M8
Random_radius_M8: RandomNumberGenerator
    MAX = 0.27
    MIN = 0.14
    PLACES = 2
    RESULT_ATTR = radius
    -> Random_mass_M8
Random_mass_M8: RandomNumberGenerator
    MAX = 0.21
    MIN = 0.05
    PLACES = 2
    RESULT_ATTR = mass
    -> Random_lum_M8
Random_lum_M8: RandomNumberGenerator
    MAX = 0.011
    MIN = 0.001
    PLACES = 3
    RESULT_ATTR = luminosity
    -> Random_hb_M8
Random_hb_M8: RandomNumberGenerator
    MAX = 0.2
    MIN = 0.10
    PLACES = 2
    RESULT_ATTR = habitable_zone
    -> SubstringExtractor

Bookmark: Cleaning
SubstringExtractor
    END = 0
    RESULT_ATTR = category0
    SRC_STRING = @Value(category)
    START = 0
    -> SubstringExtractor_2
SubstringExtractor_2
    END = 0
    RESULT_ATTR = category
    SRC_STRING = @Value(category)
    START = 0
    -> Random_num_5
AttributeCreator_47
    ATTR_TABLE:
      SET_TO name_known = FME_NULL_VALUE
      SET_TO category = Class @Value(category)
      SET_TO mass = @mult(@mult(@Value(mass),1989),1e27)
      SET_TO radius = @mult(@Value(radius),696000)
      SET_TO gs-rotation = 0
      SET_TO category1 = S
      SET_TO gs-size = @round(@div(@sum(@Value(radius),1713200),4096500),2)
    -> AttributeCreator_38
AttributeCreator_38
    ATTR_TABLE = SET_TO gs-size = FME_CONDITIONAL:DEFAULT_VALUE'@Value(gs-size)'BOOL_OP;OR;COMPOSITE_TEST;<Unused>;TEST @Value(gs-size) < 0.3'0.3'BOOL_OP;OR;COMPOSITE_TEST;<Unused>;TEST @Value(gs-size) > 2'2'FME_NUM_CONDITIONS3___
    -> AttributeRounder
AttributeRounder
    PLACES = 0
    ROUND_TYPE = Nearest
    SRC_ATTRS = radius habitable_zone mass
    -> Tester

Bookmark: Star name
Random_num_5: RandomNumberGenerator
    MAX = 9
    MIN = 0
    PLACES = 0
    RESULT_ATTR = _random_number
    -> Random_num_7
Random_num_7: RandomNumberGenerator
    MAX = 9
    MIN = 0
    PLACES = 0
    RESULT_ATTR = _random_number2
    -> RandomLetter_3
RandomLetter_3: RandomNumberGenerator
    MAX = 26
    MIN = 1
    PLACES = 0
    RESULT_ATTR = _random_letter
    -> StringPairReplacer_21
StringPairReplacer_21
    CASE = no
    MAP:
      26 Z
      25 Y
      24 X
      23 W
      22 V
      21 U
      20 T
      19 S
      18 R
      17 Q
      16 P
      15 O
      14 N
      13 M
      12 L
      11 K
      10 J
      9 I
      8 H
      7 G
      6 F
      5 E
      4 D
      3 C
      2 B
      1 A
    RESULT_ATTR = _random_letter
    SRC_ATTR = _random_letter
    -> Random_num_6
Random_num_6: RandomNumberGenerator
    MAX = 9
    MIN = 0
    PLACES = 0
    RESULT_ATTR = _random_number3
    -> Random_num_8
Random_num_8: RandomNumberGenerator
    MAX = 9
    MIN = 0
    PLACES = 0
    RESULT_ATTR = _random_number4
    -> RandomLetter_4
RandomLetter_4: RandomNumberGenerator
    MAX = 26
    MIN = 1
    PLACES = 0
    RESULT_ATTR = _random_letter2
    -> StringPairReplacer_22
StringPairReplacer_22
    CASE = no
    MAP:
      26 Z
      25 Y
      24 X
      23 W
      22 V
      21 U
      20 T
      19 S
      18 R
      17 Q
      16 P
      15 O
      14 N
      13 M
      12 L
      11 K
      10 J
      9 I
      8 H
      7 G
      6 F
      5 E
      4 D
      3 C
      2 B
      1 A
    RESULT_ATTR = _random_letter2
    SRC_ATTR = _random_letter2
    -> AttributeCreator_35
AttributeCreator_35
    ATTR_TABLE = SET_TO name_generated = S@Value(category0)-@Value(_random_number)@Value(_random_number2)@Value(_random_number3)@Value(_random_number4)@Value(_random_letter)
    -> AttributeCreator_47

Bookmark: Comets
Random_rotation: RandomNumberGenerator
    MAX = 360
    MIN = 0
    PLACES = 0
    RESULT_ATTR = gs-rotation
    -> Random_type_2
Random_type_2: RandomNumberGenerator
    MAX = 10
    MIN = 1
    PLACES = 0
    RESULT_ATTR = category0
    -> StringPairReplacer_6
StringPairReplacer_6
    CASE = no
    MAP:
      10 comet1
      9 comet1
      8 comet2
      7 comet2
      6 comet3
      5 comet3
      4 comet4
      3 comet4
      2 comet5
      1 comet5
    RESULT_ATTR = gs-color_halo
    SRC_ATTR = category0
    -> StringPairReplacer_7
StringPairReplacer_7
    CASE = no
    MAP:
      10 #B9BAB
      9 #B9BAB
      8 #928d8d
      7 #6b6b6b
      6 #d6d6d6
      5 #9f9f9f
      4 #a57575
      3 #88a575
      2 #ba3a02
      1 #989898
    RESULT_ATTR = gs-color
    SRC_ATTR = category0
    -> StringPairReplacer_5
StringPairReplacer_5
    CASE = no
    MAP:
      10 P
      9 P
      8 C
      7 C
      6 X
      5 X
      4 X
      3 D
      2 D
      1 D
    RESULT_ATTR = category
    SRC_ATTR = category0
    -> StringPairReplacer_18
StringPairReplacer_18
    CASE = no
    MAP:
      10 P
      9 P
      8 C
      7 C
      6 X
      5 X
      4 X
      3 D
      2 D
      1 D
    RESULT_ATTR = category0
    SRC_ATTR = category0
    -> AttributeCreator_45
AttributeCreator_45
    ATTR_TABLE:
      SET_TO celestial_body = comet
      SET_TO orbiter_count = 0
    -> Random_radius_2
Random_radius_2: RandomNumberGenerator
    MAX = 20
    MIN = 5
    PLACES = 0
    RESULT_ATTR = radius
    -> Random_mass_2
Random_mass_2: RandomNumberGenerator
    MAX = 1000000000000000
    MIN = 10000000000000
    PLACES = 0
    RESULT_ATTR = mass
    -> Random_namenro_3
Random_namenro_3: RandomNumberGenerator
    MAX = 99999
    MIN = 100
    PLACES = 0
    RESULT_ATTR = namenro
    -> Random_rotation_4
Random_rotation_4: RandomNumberGenerator
    MAX = 100
    MIN = 0.1
    PLACES = 1
    RESULT_ATTR = rotation
    -> AttributeCreator_6
AttributeCreator_6
    ATTR_TABLE:
      SET_TO name_generated = C-@Value(category)@Value(namenro)
      SET_TO name_known = FME_NULL_VALUE
      SET_TO category = @Value(category)-comet
      SET_TO habitable_zone = Not located in the habitable zone
      SET_TO distance = FME_NULL_VALUE
      SET_TO orbital_period = FME_NULL_VALUE
      SET_TO atmosphere = No
      SET_TO luminosity = 0
      SET_TO atm_pressure = 0
      SET_TO category1 = C
    -> DuplicateFilter_3
DuplicateFilter_3
    INPUT_ORDERED_CHOICE = No
    KEYATTR = name_generated
    UNIQUE -> Random_type_6
    DUPLICATE -> Duplicate_Names_AsteroidComet

Bookmark: Asteroids
Random_type: RandomNumberGenerator
    MAX = 10
    MIN = 1
    PLACES = 0
    RESULT_ATTR = category0
    -> StringPairReplacer_4
StringPairReplacer_4
    CASE = no
    MAP:
      10 #B9BAB
      9 #B9BAB
      8 #928d8d
      7 #6b6b6b
      6 #d6d6d6
      5 #9f9f9f
      4 #a57575
      3 #88a575
      2 #ba3a02
      1 #989898
    RESULT_ATTR = gs-color
    SRC_ATTR = category0
    -> StringPairReplacer_25
StringPairReplacer_25
    CASE = no
    MAP:
      10 B9BAB
      9 B9BAB
      8 928d8d
      7 6b6b6b
      6 d6d6d6
      5 9f9f9f
      4 a57575
      3 88a575
      2 ba3a02
      1 989898
    RESULT_ATTR = gs-color_halo
    SRC_ATTR = category0
    -> StringPairReplacer_16
StringPairReplacer_16
    CASE = no
    MAP:
      10 C
      9 C
      8 C
      7 C
      6 C
      5 C
      4 S
      3 S
      2 M
      1 V
    RESULT_ATTR = category
    SRC_ATTR = category0
    -> StringPairReplacer_3
StringPairReplacer_3
    CASE = no
    MAP:
      10 C
      9 C
      8 C
      7 C
      6 C
      5 C
      4 S
      3 S
      2 M
      1 V
    RESULT_ATTR = category0
    SRC_ATTR = category0
    -> AttributeCreator_5
AttributeCreator_5
    ATTR_TABLE:
      SET_TO celestial_body = asteroid
      SET_TO orbiter_count = 0
    -> Random_radius
Random_radius: RandomNumberGenerator
    MAX = 1000
    MIN = 30
    PLACES = 0
    RESULT_ATTR = radius
    -> Random_mass
Random_mass: RandomNumberGenerator
    MAX = 1000000000000000000000
    MIN = 1000000000000000
    PLACES = 0
    RESULT_ATTR = mass
    -> Random_namenro_2
Random_namenro_2: RandomNumberGenerator
    MAX = 99999
    MIN = 100
    PLACES = 0
    RESULT_ATTR = namenro
    -> Random_rotation_3
Random_rotation_3: RandomNumberGenerator
    MAX = 100
    MIN = 0.1
    PLACES = 1
    RESULT_ATTR = rotation
    -> AttributeCreator_4
AttributeCreator_4
    ATTR_TABLE:
      SET_TO name_generated = A-@Value(category)@Value(namenro)
      SET_TO name_known = FME_NULL_VALUE
      SET_TO category = @Value(category)-type
      SET_TO habitable_zone = Not located in the habitable zone
      SET_TO distance = FME_NULL_VALUE
      SET_TO orbital_period = FME_NULL_VALUE
      SET_TO atmosphere = No
      SET_TO luminosity = 0
      SET_TO gs-rotation = 0
      SET_TO atm_pressure = 0
      SET_TO category1 = A
    -> DuplicateFilter_2
DuplicateFilter_2
    INPUT_ORDERED_CHOICE = No
    KEYATTR = name_generated
    UNIQUE -> Random_temperature_2
    DUPLICATE -> Duplicate_Names_AsteroidComet
Random_temperature_2: RandomNumberGenerator
    MAX = 90
    MIN = 50
    PLACES = 0
    RESULT_ATTR = temperature
    -> AttributeRounder

Bookmark: Planet creation
Tester
    BOOL_OP = OR
    TEST_CLAUSE = TEST @Value(orbiter_count) = 0
    PASSED -> AttributeKeeper
    FAILED -> Cloner
Cloner
    COPIES = @sum(@Value(orbiter_count),1)
    COPYATT = _copynum
    COPY -> Tester_2
Tester_2
    BOOL_OP = OR
    TEST_CLAUSE = TEST @Value(_copynum) = 0
    PASSED -> AttributeCreator_16
    FAILED -> Random_x2
AttributeCreator_16
    ATTR_TABLE = SET_TO habitable_zone = @Value(habitable_zone) AU
    -> AttributeKeeper
Random_x2: RandomNumberGenerator
    MAX = 20000
    MIN = 2000
    PLACES = 0
    RESULT_ATTR = x2
    -> Random_y2
Random_y2: RandomNumberGenerator
    MAX = 20000
    MIN = 2000
    PLACES = 0
    RESULT_ATTR = y2
    -> Random_plusminusx
Random_plusminusx: RandomNumberGenerator
    MAX = 1
    MIN = 0
    PLACES = 0
    RESULT_ATTR = plusminusx
    -> Random_plusminusy
Random_plusminusy: RandomNumberGenerator
    MAX = 1
    MIN = 0
    PLACES = 0
    RESULT_ATTR = plusminusy
    -> StringReplacer
StringReplacer
    CASE = NO
    FIND_TEXT = 0
    NO_MATCH = _FME_NO_OP_
    REGEXP = NO
    REPLACE_TEXT = -1
    SRC_ATTRS = plusminusx,plusminusy
    -> AttributeCreator_
AttributeCreator_
    ATTR_TABLE:
      SET_TO x3 = @sum(@Value(x),@mult(@mult(@Value(x2),@Value(_copynum)),@Value(plusminusx)))
      SET_TO y3 = @sum(@Value(y),@mult(@mult(@Value(y2),@Value(_copynum)),@Value(plusminusy)))
    -> Tester_6
Tester_6
    BOOL_OP = OR
    TEST_CLAUSE = TEST @Value(x3) < -20026376.39
    PASSED -> AttributeCreator_10
    FAILED -> Tester_7
AttributeCreator_10
    ATTR_TABLE = SET_TO x3 = -20026376.39
    -> Tester_8
Tester_7
    BOOL_OP = OR
    TEST_CLAUSE = "TEST @Value(x3) > 20026376.39 "
    PASSED -> AttributeCreator_11
    FAILED -> CoordinateReplacer_3
AttributeCreator_11
    ATTR_TABLE = SET_TO x3 = 20026376.39
    -> Tester_8
Tester_8
    BOOL_OP = OR
    TEST_CLAUSE = TEST @Value(y3) < -20026376.39
    PASSED -> AttributeCreator_12
    FAILED -> Tester_9
AttributeCreator_12
    ATTR_TABLE = SET_TO y3 = -20026376.39
    -> CoordinateReplacer_3
Tester_9
    BOOL_OP = OR
    TEST_CLAUSE = "TEST @Value(y3) > 20026376.39 "
    PASSED -> AttributeCreator_13
    FAILED -> CoordinateReplacer_3
AttributeCreator_13
    ATTR_TABLE = SET_TO y3 = 20026376.39
    -> CoordinateReplacer_3
CoordinateReplacer_3
    FIND_X = @Value(x)
    FIND_Y = @Value(y)
    REPLACE_X = @Value(x3)
    REPLACE_Y = @Value(y3)
    -> Size_2

Bookmark: Geoserver stuff planets
Size_2: RandomNumberGenerator
    MAX = 1
    MIN = 0.3
    PLACES = 1
    RESULT_ATTR = gs-size
    -> Size_scale_2
Size_scale_2: RandomNumberGenerator
    MAX = 1.2
    MIN = 1.2
    PLACES = 1
    RESULT_ATTR = gs-size_scale
    -> Size_halo_2
Size_halo_2: RandomNumberGenerator
    MAX = 2
    MIN = 1
    PLACES = 1
    RESULT_ATTR = gs-size_halo
    -> Fill_opacity_2
Fill_opacity_2: RandomNumberGenerator
    MAX = 0.7
    MIN = 0.4
    PLACES = 1
    RESULT_ATTR = gs-fill_opaci
    -> AttributeCreator_27
AttributeCreator_27
    ATTR_TABLE:
      SET_TO gs-color_halo = FME_NULL_VALUE
      SET_TO category1 = P
      SET_TO satellite_of = @Value(name_generated)
    -> Sampler

Bookmark: Planet variables
Sampler
    RATE = 5
    SAMPLE_MODE = Yes
    SAMPLE_TYPE_LONG = Every Nth Feature
    SAMPLED -> Random_moon_count_2
    NOT_SAMPLED -> Random_moon_count
Random_moon_count_2: RandomNumberGenerator
    MAX = 2
    MIN = 0
    PLACES = 0
    RESULT_ATTR = orbiter_count
    -> Random_namenro_4
Random_moon_count: RandomNumberGenerator
    MAX = 1
    MIN = 0
    PLACES = 0
    RESULT_ATTR = orbiter_count
    -> Random_namenro_4
Random_namenro_4: RandomNumberGenerator
    MAX = 99999
    MIN = 100
    PLACES = 0
    RESULT_ATTR = namenro
    -> Tester_3
Tester_3
    BOOL_OP = AND
    TEST_CLAUSE:
      TEST @Value(_copynum) = 1
      TEST @Value(x2) < 5000
      TEST @Value(y2) < 5000
    PASSED -> AttributeCreator_7
    FAILED -> Tester_4
AttributeCreator_7
    ATTR_TABLE:
      SET_TO category = CH
      SET_TO gs-color = #d00b0b
      SET_TO category0 = CH
    -> Random_type_5
Tester_4
    BOOL_OP = AND
    TEST_CLAUSE:
      TEST @Value(_copynum) <= 4
      TEST @Value(x2) < 7000
      TEST @Value(y2) < 7000
    PASSED -> AttributeCreator_9
    FAILED -> Random_type_3
AttributeCreator_9
    ATTR_TABLE:
      SET_TO category = TE
      SET_TO gs-color = #00a599
      SET_TO category0 = TE
    -> Random_type_4
Random_type_3: RandomNumberGenerator
    MAX = 15
    MIN = 2
    PLACES = 0
    RESULT_ATTR = category0
    -> StringPairReplacer_9
StringPairReplacer_9
    CASE = no
    MAP:
      15 #6d4631
      14 #878685
      13 #f2d07f
      12 #ea5f13
      11 #d67e57
      10 #b89f94
      9 #b2dffb
      8 #5bd2ff
      7 #5a6265
      6 #a13100
      5 #2152ff
      4 #a5a9b8
      3 #a494cc
      2 #c5a006
    RESULT_ATTR = gs-color
    SRC_ATTR = category0
    -> StringPairReplacer_8
StringPairReplacer_8
    CASE = no
    MAP:
      15 CA
      14 CO
      13 DE
      12 GD
      11 GG
      10 HE
      9 IG
      8 IC
      7 IR
      6 LA
      5 OC
      4 PR
      3 PU
      2 SI
    RESULT_ATTR = category
    SRC_ATTR = category0
    -> StringPairReplacer_19
StringPairReplacer_19
    CASE = no
    MAP:
      15 CA
      14 CO
      13 DE
      12 GD
      11 GG
      10 HE
      9 IG
      8 IC
      7 IR
      6 LA
      5 OC
      4 PR
      3 PU
      2 SI
    RESULT_ATTR = category0
    SRC_ATTR = category0
    -> Tester_10
Tester_10
    BOOL_OP = OR
    TEST_CLAUSE:
      TEST @Value(category) = CA
      TEST @Value(category) = DE
      TEST @Value(category) = IC
      TEST @Value(category) = IR
      TEST @Value(category) = OC
      TEST @Value(category) = SI
    PASSED -> Random_type_4
    FAILED -> Tester_11
Random_type_4: RandomNumberGenerator
    MAX = 5
    MIN = 1
    PLACES = 0
    RESULT_ATTR = atmosphere
    -> StringPairReplacer_11
StringPairReplacer_11
    CASE = no
    MAP:
      1 Oxygen,\ Natrium,\ Hydrogen
      2 Carbon\ dioxide,\ Nitrogen
      3 Nitrogen,\ Oxygen,\ Argon
      4 Carbon\ dioxide,\ Nitrogen,\ Argon
      5 Nitrogen,\ Oxygen,\ Carbon\ dioxide
    RESULT_ATTR = atmosphere
    SRC_ATTR = atmosphere
    -> AttributeCreator_8
Tester_11
    BOOL_OP = OR
    TEST_CLAUSE:
      TEST @Value(category) = CO
      TEST @Value(category) = GD
      TEST @Value(category) = GG
      TEST @Value(category) = IG
      TEST @Value(category) = LA
      TEST @Value(category) = PR
      TEST @Value(category) = PU
    PASSED -> Random_type_5
    FAILED -> AttributeCreator_18
Random_type_5: RandomNumberGenerator
    MAX = 4
    MIN = 2
    PLACES = 0
    RESULT_ATTR = atmosphere
    -> StringPairReplacer_12
AttributeCreator_18
    ATTR_TABLE = SET_TO atmosphere = 1
    -> StringPairReplacer_12
StringPairReplacer_12
    CASE = no
    MAP:
      1 Helium,\ Hydrogen
      2 Hydrogen,\ Helium
      3 Hydrogen,\ Helium,\ Methane
      4 Natrium,\ Oxygen,\ Silicon\ monoxide
      5 Hydrogen,\ Helium,\ Sulfur
      6 Methane,\ Nitrogen
    RESULT_ATTR = atmosphere
    SRC_ATTR = atmosphere
    -> AttributeCreator_8
AttributeCreator_8
    ATTR_TABLE:
      SET_TO name_generated = P-@Value(category)@Value(namenro)
      SET_TO name_known = FME_NULL_VALUE
      SET_TO celestial_body = planet
    -> VertexCreator
VertexCreator
    MODE_NAME = Add Point
    XVAL = @Value(x)
    YVAL = @Value(y)
    -> LengthCalculator
LengthCalculator
    DIM = 2
    LEN_ATTR = _length
    MULT = 1
    -> VertexRemover
VertexRemover
    IND = -1
    KEEP_REMOVE_PARAM = Remove
    LEN = 1
    -> Tester_5
Tester_5
    BOOL_OP = AND
    TEST_CLAUSE:
      TEST @Value(_length) > @mult(@mult(3735,@Value(habitable_zone)),0.8)
      TEST @Value(_length) < @mult(@mult(3735,@Value(habitable_zone)),1.2)
    PASSED -> AttributeCreator_14
    FAILED -> AttributeCreator_15
AttributeCreator_14
    ATTR_TABLE = SET_TO habitable_zone = Located in the habitable zone
    -> Random_temp
AttributeCreator_15
    ATTR_TABLE = SET_TO habitable_zone = Not located in the habitable zone
    -> Random_temp
Random_temp: RandomNumberGenerator
    MAX = FME_CONDITIONAL:DEFAULT_VALUE'300'BOOL_OP;OR;COMPOSITE_TEST;<Unused>;TEST @Value(category) = CH'28000'BOOL_OP;OR;COMPOSITE_TEST;<Unused>;TEST @Value(category) = CA'400'BOOL_OP;OR;COMPOSITE_TEST;<Unused>;TEST @Value(category) = CO'1000'BOOL_OP;OR;COMPOSITE_TEST;<Unused>;TEST @Value(category) = DE'350'BOOL_OP;OR;COMPOSITE_TEST;<Unused>;TEST @Value(category) = GD'450'BOOL_OP;OR;COMPOSITE_TEST;<Unused>;TEST @Value(category) = GG;TEST @Value(category) = IC'260'BOOL_OP;OR;COMPOSITE_TEST;<Unused>;TEST @Value(category) = HE'4000'BOOL_OP;OR;COMPOSITE_TEST;<Unused>;TEST @Value(category) = IG'90'BOOL_OP;OR;COMPOSITE_TEST;<Unused>;TEST @Value(category) = IR'600'BOOL_OP;OR;COMPOSITE_TEST;<Unused>;TEST @Value(category) = LA'1800'BOOL_OP;OR;COMPOSITE_TEST;<Unused>;TEST @Value(category) = OC'320'BOOL_OP;OR;COMPOSITE_TEST;<Unused>;TEST @Value(category) = PR'235'BOOL_OP;OR;COMPOSITE_TEST;<Unused>;TEST @Value(category) = PU'4600'BOOL_OP;OR;COMPOSITE_TEST;<Unused>;TEST @Value(category) = SI;TEST @Value(category) = TE'800'FME_NUM_CONDITIONS15___
    MIN = FME_CONDITIONAL:DEFAULT_VALUE'0'BOOL_OP;OR;COMPOSITE_TEST;<Unused>;TEST @Value(category) = CH'27400'BOOL_OP;OR;COMPOSITE_TEST;<Unused>;TEST @Value(category) = CA;TEST @Value(category) = CO;TEST @Value(category) = SI;TEST @Value(category) = TE'250'BOOL_OP;OR;COMPOSITE_TEST;<Unused>;TEST @Value(category) = DE'200'BOOL_OP;OR;COMPOSITE_TEST;<Unused>;TEST @Value(category) = GD'350'BOOL_OP;OR;COMPOSITE_TEST;<Unused>;TEST @Value(category) = GG'80'BOOL_OP;OR;COMPOSITE_TEST;<Unused>;TEST @Value(category) = HE'3000'BOOL_OP;OR;COMPOSITE_TEST;<Unused>;TEST @Value(category) = IG;TEST @Value(category) = IC;TEST @Value(category) = OC'50'BOOL_OP;OR;COMPOSITE_TEST;<Unused>;TEST @Value(category) = IR'400'BOOL_OP;OR;COMPOSITE_TEST;<Unused>;TEST @Value(category) = LA'1300'BOOL_OP;OR;COMPOSITE_TEST;<Unused>;TEST @Value(category) = PR'150'BOOL_OP;OR;COMPOSITE_TEST;<Unused>;TEST @Value(category) = PU'1000'FME_NUM_CONDITIONS12___
    PLACES = 0
    RESULT_ATTR = temperature
    -> Random_rotation_2
    <REJECTED> -> Random_rotation_2
Random_rotation_2: RandomNumberGenerator
    MAX = 100
    MIN = 0.1
    PLACES = 1
    RESULT_ATTR = rotation
    -> Random_orbital_period_5
Random_orbital_period_5: RandomNumberGenerator
    MAX = 500
    MIN = 0.1
    PLACES = 1
    RESULT_ATTR = orbital_period
    -> Random_radius_3
Random_radius_3: RandomNumberGenerator
    MAX = FME_CONDITIONAL:DEFAULT_VALUE'2'BOOL_OP;OR;COMPOSITE_TEST;<Unused>;TEST @Value(category) = CH;TEST @Value(category) = HE;TEST @Value(category) = LA'3'BOOL_OP;OR;COMPOSITE_TEST;<Unused>;TEST @Value(category) = CA;TEST @Value(category) = DE;TEST @Value(category) = SI;TEST @Value(category) = TE'1.5'BOOL_OP;OR;COMPOSITE_TEST;<Unused>;TEST @Value(category) = CO'0.9'BOOL_OP;OR;COMPOSITE_TEST;<Unused>;TEST @Value(category) = GD'3.9'BOOL_OP;OR;COMPOSITE_TEST;<Unused>;TEST @Value(category) = GG;TEST @Value(category) = PU'20'BOOL_OP;OR;COMPOSITE_TEST;<Unused>;TEST @Value(category) = IG'5'BOOL_OP;OR;COMPOSITE_TEST;<Unused>;TEST @Value(category) = IC'1.2'BOOL_OP;OR;COMPOSITE_TEST;<Unused>;TEST @Value(category) = IR'0.5'BOOL_OP;OR;COMPOSITE_TEST;<Unused>;TEST @Value(category) = OC'2'BOOL_OP;OR;COMPOSITE_TEST;<Unused>;TEST @Value(category) = PR'0.6'FME_NUM_CONDITIONS11___
    MIN = FME_CONDITIONAL:DEFAULT_VALUE'0.8'BOOL_OP;OR;COMPOSITE_TEST;<Unused>;TEST @Value(category) = CH;TEST @Value(category) = LA'1'BOOL_OP;OR;COMPOSITE_TEST;<Unused>;TEST @Value(category) = CA'0.7'BOOL_OP;OR;COMPOSITE_TEST;<Unused>;TEST @Value(category) = CO'0.5'BOOL_OP;OR;COMPOSITE_TEST;<Unused>;TEST @Value(category) = DE'0.4'BOOL_OP;OR;COMPOSITE_TEST;<Unused>;TEST @Value(category) = GD'1.2'BOOL_OP;OR;COMPOSITE_TEST;<Unused>;TEST @Value(category) = GG;TEST @Value(category) = PU'5'BOOL_OP;OR;COMPOSITE_TEST;<Unused>;TEST @Value(category) = HE;TEST @Value(category) = IR;TEST @Value(category) = SI;TEST @Value(category) = TE'0.3'BOOL_OP;OR;COMPOSITE_TEST;<Unused>;TEST @Value(category) = IG'3'BOOL_OP;OR;COMPOSITE_TEST;<Unused>;TEST @Value(category) = IC'0.1'BOOL_OP;OR;COMPOSITE_TEST;<Unused>;TEST @Value(category) = OC;TEST @Value(category) = PR'0.2'FME_NUM_CONDITIONS11___
    PLACES = 2
    RESULT_ATTR = radius
    -> Random_mass_3
Random_mass_3: RandomNumberGenerator
    MAX = FME_CONDITIONAL:DEFAULT_VALUE'1.2'BOOL_OP;OR;COMPOSITE_TEST;<Unused>;TEST @Value(category) = CH'100'BOOL_OP;OR;COMPOSITE_TEST;<Unused>;TEST @Value(category) = CA;TEST @Value(category) = SI;TEST @Value(category) = TE;TEST @Value(category) = OC'1.5'BOOL_OP;OR;COMPOSITE_TEST;<Unused>;TEST @Value(category) = CO;TEST @Value(category) = HE'0.4'BOOL_OP;OR;COMPOSITE_TEST;<Unused>;TEST @Value(category) = DE'0.9'BOOL_OP;OR;COMPOSITE_TEST;<Unused>;TEST @Value(category) = GD'0.8'BOOL_OP;OR;COMPOSITE_TEST;<Unused>;TEST @Value(category) = GG'400'BOOL_OP;OR;COMPOSITE_TEST;<Unused>;TEST @Value(category) = IG'20'BOOL_OP;OR;COMPOSITE_TEST;<Unused>;TEST @Value(category) = IC'1.2'BOOL_OP;OR;COMPOSITE_TEST;<Unused>;TEST @Value(category) = IR'0.08'BOOL_OP;OR;COMPOSITE_TEST;<Unused>;TEST @Value(category) = LA'9'BOOL_OP;OR;COMPOSITE_TEST;<Unused>;TEST @Value(category) = PR'0.6'BOOL_OP;OR;COMPOSITE_TEST;<Unused>;TEST @Value(category) = PU'4000'FME_NUM_CONDITIONS13___
    MIN = FME_CONDITIONAL:DEFAULT_VALUE'0.8'BOOL_OP;OR;COMPOSITE_TEST;<Unused>;TEST @Value(category) = CH'30'BOOL_OP;OR;COMPOSITE_TEST;<Unused>;TEST @Value(category) = CA'0.7'BOOL_OP;OR;COMPOSITE_TEST;<Unused>;TEST @Value(category) = CO'0.2'BOOL_OP;OR;COMPOSITE_TEST;<Unused>;TEST @Value(category) = DE'0.1'BOOL_OP;OR;COMPOSITE_TEST;<Unused>;TEST @Value(category) = GD'0.4'BOOL_OP;OR;COMPOSITE_TEST;<Unused>;TEST @Value(category) = GG'50'BOOL_OP;OR;COMPOSITE_TEST;<Unused>;TEST @Value(category) = HE'0.3'BOOL_OP;OR;COMPOSITE_TEST;<Unused>;TEST @Value(category) = IG'10'BOOL_OP;OR;COMPOSITE_TEST;<Unused>;TEST @Value(category) = IC'0.002'BOOL_OP;OR;COMPOSITE_TEST;<Unused>;TEST @Value(category) = IR;TEST @Value(category) = SI;TEST @Value(category) = TE'0.05'BOOL_OP;OR;COMPOSITE_TEST;<Unused>;TEST @Value(category) = LA'0.9'BOOL_OP;OR;COMPOSITE_TEST;<Unused>;TEST @Value(category) = OC;TEST @Value(category) = PR'0.008'BOOL_OP;OR;COMPOSITE_TEST;<Unused>;TEST @Value(category) = PU'300'FME_NUM_CONDITIONS14___
    PLACES = 3
    RESULT_ATTR = mass
    -> Random_atm_pressure
Random_atm_pressure: RandomNumberGenerator
    MAX = FME_CONDITIONAL:DEFAULT_VALUE'1.2'BOOL_OP;OR;COMPOSITE_TEST;<Unused>;TEST @Value(category) = CA;TEST @Value(category) = DE;TEST @Value(category) = IC;TEST @Value(category) = IR;TEST @Value(category) = SI'100'BOOL_OP;OR;COMPOSITE_TEST;<Unused>;TEST @Value(category) = OC;TEST @Value(category) = TE'1.2'BOOL_OP;OR;COMPOSITE_TEST;<Unused>;TEST @Value(category) = CH;TEST @Value(category) = CO;TEST @Value(category) = PR'0.01'BOOL_OP;OR;COMPOSITE_TEST;<Unused>;TEST @Value(category) = LA'1'BOOL_OP;OR;COMPOSITE_TEST;<Unused>;TEST @Value(category) = PU;TEST @Value(category) = GD;TEST @Value(category) = GG;TEST @Value(category) = HE;TEST @Value(category) = IG'5000'FME_NUM_CONDITIONS6___
    MIN = FME_CONDITIONAL:DEFAULT_VALUE'0.8'BOOL_OP;OR;COMPOSITE_TEST;<Unused>;TEST @Value(category) = CH;TEST @Value(category) = CA;TEST @Value(category) = CO;TEST @Value(category) = DE;TEST @Value(category) = IC;TEST @Value(category) = IR;TEST @Value(category) = LA;TEST @Value(category) = PR;TEST cat = SI'0'BOOL_OP;OR;COMPOSITE_TEST;<Unused>;TEST @Value(category) = OC;TEST @Value(category) = TE'0.7'BOOL_OP;OR;COMPOSITE_TEST;<Unused>;TEST @Value(category) = GD;TEST @Value(category) = GG;TEST @Value(category) = HE;TEST @Value(category) = IG;TEST @Value(category) = PU'1000'FME_NUM_CONDITIONS4___
    PLACES = 2
    RESULT_ATTR = atm_pressure
    -> AttributeCreator_19
AttributeCreator_19
    ATTR_TABLE:
      SET_TO gs-size = @round((@Value(radius)/20+@Value(radius)/0.1*0.035+0.2),2)




      SET_TO gs-color_halo = @ReplaceString(@Value(gs-color),"#","")
    -> Tester_12
Tester_12
    BOOL_OP = OR
    TEST_CLAUSE = TEST @Value(gs-size) > 1
    PASSED -> AttributeCreator_17
    FAILED -> Tester_20
AttributeCreator_17
    ATTR_TABLE:
      SET_TO distance = @div(@Value(_length),3735)
      SET_TO radius = @mult(@Value(radius),6370)
      SET_TO mass = @mult(@mult(@Value(mass),5974),1e21)
      SET_TO x = @Value(x3)
      SET_TO y = @Value(y3)
      SET_TO gs-size = 1.1
    -> StringPairReplacer_13
Tester_20
    BOOL_OP = OR
    TEST_CLAUSE = TEST @Value(gs-size) < 0.4
    PASSED -> AttributeCreator_20
    FAILED -> AttributeCreator_34
AttributeCreator_20
    ATTR_TABLE:
      SET_TO distance = @div(@Value(_length),3735)
      SET_TO radius = @mult(@Value(radius),6370)
      SET_TO mass = @mult(@mult(@Value(mass),5974),1e21)
      SET_TO x = @Value(x3)
      SET_TO y = @Value(y3)
    -> StringPairReplacer_13
AttributeCreator_34
    ATTR_TABLE:
      SET_TO distance = @div(@Value(_length),3735)
      SET_TO radius = @mult(@Value(radius),6370)
      SET_TO mass = @mult(@mult(@Value(mass),5974),1e21)
      SET_TO x = @Value(x3)
      SET_TO y = @Value(y3)
      SET_TO gs-size = 0.55
    -> StringPairReplacer_13
StringPairReplacer_13
    CASE = no
    MAP:
      CH Chthonian\ planet
      CA Carbon\ planet
      CO Coreless\ planet
      DE Desert\ planet
      GD Gas\ dwarf\ planet
      GG Gas\ giant\ planet
      HE Helium\ planet
      IG Ice\ giant\ planet
      IC Ice\ planet
      IR Iron\ planet
      LA Lava\ planet
      OC Ocean\ planet
      PR Protoplanet
      PU Puffy\ planet
      SI Silicate\ planet
      TE Terrestrial\ planet
    RESULT_ATTR = category
    SRC_ATTR = category
    -> Random_num_9

Bookmark: Star name
Random_num_9: RandomNumberGenerator
    MAX = 9
    MIN = 0
    PLACES = 0
    RESULT_ATTR = _random_number
    -> Random_num_11
Random_num_11: RandomNumberGenerator
    MAX = 9
    MIN = 0
    PLACES = 0
    RESULT_ATTR = _random_number2
    -> RandomLetter_5
RandomLetter_5: RandomNumberGenerator
    MAX = 26
    MIN = 1
    PLACES = 0
    RESULT_ATTR = _random_letter
    -> StringPairReplacer_23
StringPairReplacer_23
    CASE = no
    MAP:
      26 Z
      25 Y
      24 X
      23 W
      22 V
      21 U
      20 T
      19 S
      18 R
      17 Q
      16 P
      15 O
      14 N
      13 M
      12 L
      11 K
      10 J
      9 I
      8 H
      7 G
      6 F
      5 E
      4 D
      3 C
      2 B
      1 A
    RESULT_ATTR = _random_letter
    SRC_ATTR = _random_letter
    -> Random_num_10
Random_num_10: RandomNumberGenerator
    MAX = 9
    MIN = 0
    PLACES = 0
    RESULT_ATTR = _random_number3
    -> Random_num_12
Random_num_12: RandomNumberGenerator
    MAX = 9
    MIN = 0
    PLACES = 0
    RESULT_ATTR = _random_number4
    -> RandomLetter_6
RandomLetter_6: RandomNumberGenerator
    MAX = 26
    MIN = 1
    PLACES = 0
    RESULT_ATTR = _random_letter2
    -> StringPairReplacer_24
StringPairReplacer_24
    CASE = no
    MAP:
      26 Z
      25 Y
      24 X
      23 W
      22 V
      21 U
      20 T
      19 S
      18 R
      17 Q
      16 P
      15 O
      14 N
      13 M
      12 L
      11 K
      10 J
      9 I
      8 H
      7 G
      6 F
      5 E
      4 D
      3 C
      2 B
      1 A
    RESULT_ATTR = _random_letter2
    SRC_ATTR = _random_letter2
    -> AttributeCreator_37
AttributeCreator_37
    ATTR_TABLE = SET_TO name_generated = P-@Value(category0)@Value(_random_number)@Value(_random_number2)-@Value(_random_letter)@Value(_random_letter2)@Value(_random_number3)@Value(_random_number4)
    -> Tester_13

Bookmark: Moon creation
Tester_13
    BOOL_OP = OR
    TEST_CLAUSE = TEST @Value(orbiter_count) = 0
    PASSED -> AttributeKeeper
    FAILED -> Cloner_2
Cloner_2
    COPIES = @sum(@Value(orbiter_count),1)
    COPYATT = _copynum
    COPY -> Tester_14
Tester_14
    BOOL_OP = OR
    TEST_CLAUSE = TEST @Value(_copynum) = 0
    PASSED -> AttributeKeeper
    FAILED -> Random_x2_2
Random_x2_2: RandomNumberGenerator
    MAX = 6000
    MIN = 600
    PLACES = 0
    RESULT_ATTR = x2
    -> Random_y2_2
Random_y2_2: RandomNumberGenerator
    MAX = 6000
    MIN = 600
    PLACES = 0
    RESULT_ATTR = y2
    -> Random_plusminusx_2
Random_plusminusx_2: RandomNumberGenerator
    MAX = 1
    MIN = 0
    PLACES = 0
    RESULT_ATTR = plusminusx
    -> Random_plusminusy_2
Random_plusminusy_2: RandomNumberGenerator
    MAX = 1
    MIN = 0
    PLACES = 0
    RESULT_ATTR = plusminusy
    -> StringReplacer_2
StringReplacer_2
    CASE = NO
    FIND_TEXT = 0
    NO_MATCH = _FME_NO_OP_
    REGEXP = NO
    REPLACE_TEXT = -1
    SRC_ATTRS = plusminusx,plusminusy
    -> AttributeCreator__2
AttributeCreator__2
    ATTR_TABLE:
      SET_TO x3 = @sum(@Value(x),@mult(@mult(@Value(x2),@Value(_copynum)),@Value(plusminusx)))
      SET_TO y3 = @sum(@Value(y),@mult(@mult(@Value(y2),@Value(_copynum)),@Value(plusminusy)))
    -> Tester_15
Tester_15
    BOOL_OP = OR
    TEST_CLAUSE = TEST @Value(x3) < -20026376.39
    PASSED -> AttributeCreator_21
    FAILED -> Tester_16
AttributeCreator_21
    ATTR_TABLE = SET_TO x3 = -20026376.39
    -> Tester_17
Tester_16
    BOOL_OP = OR
    TEST_CLAUSE = "TEST @Value(x3) > 20026376.39 "
    PASSED -> AttributeCreator_22
    FAILED -> CoordinateReplacer_4
AttributeCreator_22
    ATTR_TABLE = SET_TO x3 = 20026376.39
    -> Tester_17
Tester_17
    BOOL_OP = OR
    TEST_CLAUSE = TEST @Value(y3) < -20026376.39
    PASSED -> AttributeCreator_23
    FAILED -> Tester_18
AttributeCreator_23
    ATTR_TABLE = SET_TO y3 = -20026376.39
    -> CoordinateReplacer_4
Tester_18
    BOOL_OP = OR
    TEST_CLAUSE = "TEST @Value(y3) > 20026376.39 "
    PASSED -> AttributeCreator_24
    FAILED -> CoordinateReplacer_4
AttributeCreator_24
    ATTR_TABLE = SET_TO y3 = 20026376.39
    -> CoordinateReplacer_4
CoordinateReplacer_4
    FIND_X = @Value(x)
    FIND_Y = @Value(y)
    REPLACE_X = @Value(x3)
    REPLACE_Y = @Value(y3)
    -> Size_3

Bookmark: Geoserver stuff planets
Size_3: RandomNumberGenerator
    MAX = 0.7
    MIN = 0.5
    PLACES = 1
    RESULT_ATTR = gs-size
    -> Size_scale_3
Size_scale_3: RandomNumberGenerator
    MAX = 1.3
    MIN = 1.1
    PLACES = 2
    RESULT_ATTR = gs-size_scale
    -> Size_halo_3
Size_halo_3: RandomNumberGenerator
    MAX = 2
    MIN = 1
    PLACES = 1
    RESULT_ATTR = gs-size_halo
    -> Fill_opacity_3
Fill_opacity_3: RandomNumberGenerator
    MAX = 0.7
    MIN = 0.4
    PLACES = 1
    RESULT_ATTR = gs-fill_opaci
    -> AttributeCreator_29
AttributeCreator_29
    ATTR_TABLE:
      SET_TO gs-color_halo = FME_NULL_VALUE
      SET_TO satellite_of = @Value(name_generated)
    -> Random_namenro_5

Bookmark: Moon variables
Random_namenro_5: RandomNumberGenerator
    MAX = 99999
    MIN = 1000
    PLACES = 0
    RESULT_ATTR = namenro
    -> AttributeCreator_28
AttributeCreator_28
    ATTR_TABLE:
      SET_TO category = M
      SET_TO gs-color = #b2b2b2
      SET_TO celestial_body = natural satellite
      SET_TO category0 = M
    -> Random_color_2
Random_color_2: RandomNumberGenerator
    MAX = 10
    MIN = 1
    PLACES = 0
    RESULT_ATTR = gs-color
    -> StringPairReplacer_14
StringPairReplacer_14
    CASE = no
    MAP:
      10 #B9BAB
      9 #B9BAB
      8 #928d8d
      7 #6b6b6b
      6 #d6d6d6
      5 #9f9f9f
      4 #a57575
      3 #88a575
      2 #ba3a02
      1 #989898
    RESULT_ATTR = gs-color
    SRC_ATTR = gs-color
    -> Random_temp_2
Random_temp_2: RandomNumberGenerator
    MAX = 1600
    MIN = 100
    PLACES = 0
    RESULT_ATTR = temperature
    -> Random_radius_4
Random_radius_4: RandomNumberGenerator
    MAX = 2700
    MIN = 400
    PLACES = 0
    RESULT_ATTR = radius
    -> Random_mass_4
Random_mass_4: RandomNumberGenerator
    MAX = 150
    MIN = 1
    PLACES = 2
    RESULT_ATTR = mass
    -> Random_orbital_period_2
Random_orbital_period_2: RandomNumberGenerator
    MAX = 0.3
    MIN = 0.01
    PLACES = 2
    RESULT_ATTR = orbital_period
    -> Sampler_3
Sampler_3
    RATE = 5
    SAMPLE_MODE = Yes
    SAMPLE_TYPE_LONG = Every Nth Feature
    SAMPLED -> Random_atm_pressure_2
    NOT_SAMPLED -> Random_atm_pressure_3
Random_atm_pressure_2: RandomNumberGenerator
    MAX = 0.4
    MIN = 0
    PLACES = 2
    RESULT_ATTR = atm_pressure
Random_atm_pressure_3: RandomNumberGenerator
    MAX = 0.15
    MIN = 0
    PLACES = 2
    RESULT_ATTR = atm_pressure
    -> Random_atm
Random_atm: RandomNumberGenerator
    MAX = 11
    MIN = 1
    PLACES = 0
    RESULT_ATTR = atmosphere
    -> StringPairReplacer_17
StringPairReplacer_17
    CASE = no
    MAP:
      10 Carbon\ dioxide,\ Nitrogen,\ Argon
      11 Nitrogen,\ Oxygen,\ Carbon\ dioxide
      1 Helium,\ Hydrogen
      2 Hydrogen,\ Helium
      3 Hydrogen,\ Helium,\ Methane
      4 Natrium,\ Oxygen,\ Silicon\ monoxide
      5 Hydrogen,\ Helium,\ Sulfur
      6 Methane,\ Nitrogen
      7 Oxygen,\ Natrium,\ Hydrogen
      8 Carbon\ dioxide,\ Nitrogen
      9 Nitrogen,\ Oxygen,\ Argon
    RESULT_ATTR = atmosphere
    SRC_ATTR = atmosphere
    -> VertexCreator_2
VertexCreator_2
    MODE_NAME = Add Point
    XVAL = @Value(x)
    YVAL = @Value(y)
    -> LengthCalculator_2
LengthCalculator_2
    DIM = 2
    LEN_ATTR = _length
    MULT = 1
    -> VertexRemover_2
VertexRemover_2
    IND = -1
    KEEP_REMOVE_PARAM = Remove
    LEN = 1
    -> AttributeCreator_30
AttributeCreator_30
    ATTR_TABLE:
      SET_TO mass = @mult(@Value(mass),1e21)
      SET_TO rotation = @round(@mult(@Value(orbital_period),365),1)
      SET_TO name_known = FME_NULL_VALUE
      SET_TO category = Moon
      SET_TO distance = @div(@Value(_length),3735)
      SET_TO x = @Value(x3)
      SET_TO y = @Value(y3)
      SET_TO category1 = NS
      SET_TO category0 = M
      SET_TO gs-size = @round(@div(@sum(@Value(radius),750),5750),2)
    -> AttributeCreator_39
AttributeCreator_39
    ATTR_TABLE:
      SET_TO gs-size = FME_CONDITIONAL:DEFAULT_VALUE'_FME_NO_OP_'BOOL_OP;OR;COMPOSITE_TEST;<Unused>;TEST @Value(gs-size) > 0.6'0.6'FME_NUM_CONDITIONS2___
      SET_TO gs-color_halo = @ReplaceString(@Value(gs-color),"#","")
    -> AttributeKeeper

Bookmark: Orbital ring
Tester_19
    BOOL_OP = OR
    TEST_CLAUSE:
      TEST @Value(celestial_body) = sun
      TEST @Value(celestial_body) = asteroid
      TEST @Value(celestial_body) = comet
    PASSED -> AttributeCreator_26
    FAILED -> Sampler_2
Sampler_2
    RATE = 5
    SAMPLE_MODE = Yes
    SAMPLE_TYPE_LONG = Every Nth Feature
    SAMPLED -> AttributeCreator_25
    NOT_SAMPLED -> AttributeCreator_26
AttributeCreator_26
    ATTR_TABLE = SET_TO ring_system = No
    -> Random_num
AttributeCreator_25
    ATTR_TABLE = SET_TO ring_system = Yes
    -> Random_num
